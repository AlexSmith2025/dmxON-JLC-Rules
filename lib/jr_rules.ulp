// jr_rules.ulp — правила JLCPCB: значения профиля, стек слоёв, текст .dru и задание CAM
// dmxON JLC Rules · dmxON by AlexSmith 2026 · см. LICENSE.md
//
// Значения — по возможностям JLCPCB (jlcpcb.com/capabilities/pcb-capabilities) и правилам
// доплат: дорожки 3–3.5 mil на многослойных платах +20 %, отверстия меньше 0.3 мм — доплата.

// ---------------------------------------------------------------- профили

string JR_PID[] = { "Standard", "Dense", "Extreme" };     // имена в файлах и в ключе -profile

// название и смысл профиля на языке lg
string jr_pname(int lg, int p)
{
    if (p == 1) return Lx(lg, "Плотный", "Dense");
    if (p == 2) return Lx(lg, "Предельный", "Extreme");
    return Lx(lg, "Стандарт", "Standard");
}

string jr_pnote(int lg, int p)
{
    if (p == 1) return Lx(lg, "на пределе без доплат", "no-extra-cost limits");
    if (p == 2) return Lx(lg, "минимум JLCPCB, возможна доплата", "JLCPCB minimum, may cost extra");
    return Lx(lg, "с запасом, без доплат", "with margin, no extra cost");
}

real JR_THICK[] = { 0.4, 0.6, 0.8, 1.0, 1.2, 1.6, 2.0 };
int  JR_NTHICK  = 7;
real JR_OZ_IN[] = { 0.5, 1.0, 2.0 };

// ---------------------------------------------------------------- входные параметры

int  jr_n      = 2;       // слоёв меди: 2, 4, 6, 8
int  jr_prof   = 0;       // 0 Standard, 1 Dense, 2 Extreme
real jr_thick  = 1.6;     // толщина платы, мм
real jr_oo     = 1.0;     // медь снаружи, oz
real jr_oi     = 0.5;     // медь внутри, oz
int  jr_tented = 1;       // переходные под маской
int  jr_vcut   = 0;       // панель с V-cut: медь от края 0.4 мм
int  jr_lay[];            // слои меди сверху вниз (номера 1…16)

// ---------------------------------------------------------------- результат jr_calc()

real jr_tw, jr_cl, jr_smd;          // дорожка, зазор, площадки разных цепей
real jr_vd, jr_vr, jr_vri, jr_vrv;  // переходное: сверло, поясок снаружи/внутри, доля от сверла
real jr_pr, jr_pri;                 // поясок площадок выводов снаружи/внутри
real jr_edge, jr_hh, jr_mask, jr_vstop, jr_dam;
real jr_cuo, jr_cui, jr_total;
string jr_dk[];                     // P (препрег) / C (ядро)
real   jr_dt[];                     // толщина диэлектрика, мм
string jr_dg[];                     // ткань препрега
string jr_der[];                    // диэлектрическая проницаемость
int    jr_nd = 0;
string jr_snote = "";                        // замечание к стеку (нет такого у JLCPCB — взят ближайший)
string jr_warns = "";                        // предупреждения профиля (через \n)

string jr_mm(real v)
{
    return num(v) + "mm";
}

real jr_ceil01(real v)
{
    return ceil(v * 100.0 - 0.0001) / 100.0;
}

// слои по умолчанию: 6 слоёв — 1 2 3 14 15 16, 8 слоёв — 1 2 3 4 13 14 15 16
void jr_default_layers()
{
    int k = 0, half = (jr_n - 2) / 2;
    jr_lay[k++] = 1;
    for (int i = 0; i < half; i++) jr_lay[k++] = 2 + i;
    for (int j = half - 1; j >= 0; j--) jr_lay[k++] = 15 - j;
    jr_lay[k++] = 16;
}

// строка таблицы стеков для слоёв/толщины/меди или -1
int jr_stack_row(int n, real t, real oo, real oi)
{
    for (int i = 0; i < JR_NSTACK; i++) {
        string f[];
        strsplit(f, JR_STACK[i], '|');
        if (strtol(f[0]) == n && abs(strtod(f[1]) - t) < 0.01 && abs(strtod(f[2]) - oo) < 0.01 && abs(strtod(f[3]) - oi) < 0.01)
            return i;
    }
    return -1;
}

// ближайший существующий стек: сначала другая медь внутри, затем ближайшая толщина
int jr_stack_pick()
{
    jr_snote = "";
    int r = jr_stack_row(jr_n, jr_thick, jr_oo, jr_oi);
    if (r >= 0) return r;
    for (int k = 0; k < 3; k++) {
        r = jr_stack_row(jr_n, jr_thick, jr_oo, JR_OZ_IN[k]);
        if (r >= 0) {
            jr_snote = Lf("Медь внутри {0} oz для этого стека у JLCPCB нет — взято {1} oz.",
                          "Inner copper {0} oz is not offered for this stack-up — using {1} oz.", num(jr_oi), num(JR_OZ_IN[k]), "");
            jr_oi = JR_OZ_IN[k];
            return r;
        }
    }
    real bd = 100;
    int best = -1;
    for (int i = 0; i < JR_NSTACK; i++) {
        string f[];
        strsplit(f, JR_STACK[i], '|');
        if (strtol(f[0]) != jr_n || abs(strtod(f[2]) - jr_oo) > 0.01) continue;
        real d = abs(strtod(f[1]) - jr_thick) + (abs(strtod(f[3]) - jr_oi) > 0.01 ? 0.001 : 0);
        if (d < bd) { bd = d; best = i; }
    }
    if (best >= 0) {
        string g[];
        strsplit(g, JR_STACK[best], '|');
        jr_snote = Lf("Толщины {0} мм для {1} слоёв у JLCPCB нет — взято {2} мм.",
                      "{0} mm is not offered for {1} layers — using {2} mm.", num(jr_thick), istr(jr_n), g[1]);
        jr_thick = strtod(g[1]);
        jr_oi = strtod(g[3]);
    }
    return best;
}

void jr_warn(string txt)
{
    jr_warns += txt + "\n";
}

// все значения правил из входных параметров
void jr_calc()
{
    int ml = jr_n > 2;
    jr_warns = "";
    jr_snote = "";
    if (jr_lay[0] != 1) jr_default_layers();

    // стек слоёв
    jr_nd = 0;
    if (!ml) {
        jr_cuo = jr_oo >= 2 ? 0.07 : 0.035;
        jr_cui = jr_cuo;
        jr_dk[0] = "C"; jr_dt[0] = jr_thick - 2 * jr_cuo; jr_dg[0] = "FR-4"; jr_der[0] = "4.5";
        jr_nd = 1;
    }
    else {
        int r = jr_stack_pick();
        if (r >= 0) {
            string f[];
            strsplit(f, JR_STACK[r], '|');
            jr_cuo = strtod(f[4]);
            jr_cui = strtod(f[5]);
            string d[];
            int nd = strsplit(d, f[6], ' ');
            for (int i = 0; i < nd; i++) {
                string p[];
                strsplit(p, d[i], ':');
                jr_dk[jr_nd] = strsub(p[0], 0, 1);
                jr_dt[jr_nd] = strtod(strsub(p[0], 1));
                jr_dg[jr_nd] = p[1] == "core" ? "" : p[1];
                jr_der[jr_nd] = p[2];
                jr_nd++;
            }
        }
    }
    jr_total = 2 * jr_cuo + (jr_n - 2) * jr_cui;
    for (int i = 0; i < jr_nd; i++) jr_total += jr_dt[i];

    // дорожки и зазоры: решает самая толстая медь
    int heavy = jr_oo >= 2 || (ml && jr_oi >= 2);
    real free_min = heavy ? (ml ? 0.15 : 0.16) : 0.10;
    real abs_min  = heavy ? (ml ? 0.15 : 0.16) : (ml ? 0.09 : 0.10);
    if (jr_prof == 0) jr_tw = heavy ? 0.20 : 0.127;
    else if (jr_prof == 1) jr_tw = free_min;
    else jr_tw = abs_min;
    jr_cl = jr_tw;
    jr_smd = jr_prof < 2 ? max(jr_cl, 0.15) : jr_cl;

    // переходные: поясок = доля сверла, не меньше минимума
    if (jr_prof == 0) { jr_vd = 0.30; jr_vr = 0.075; jr_vrv = 0.25; }
    else if (jr_prof == 1) { jr_vd = 0.30; jr_vr = 0.05; jr_vrv = 1.0 / 6.0; }
    else { jr_vd = 0.15; jr_vr = 0.05; jr_vrv = 1.0 / 6.0; }
    // во внутренних слоях от отверстия переходного до чужой меди не меньше 0.20 мм
    jr_vri = jr_vr;
    if (ml) jr_vri = jr_ceil01(max(jr_vr, 0.20 - jr_cl));

    // площадки выводов: поясок 0.25/0.18 (2 слоя), 0.20/0.15 (многослойные), 2 oz — 0.254
    real pr_rec = ml ? 0.20 : 0.25, pr_min = ml ? 0.15 : 0.18;
    if (heavy) { pr_rec = 0.26; pr_min = 0.26; }
    jr_pr = jr_prof == 0 ? pr_rec : pr_min;
    // внутри: от отверстия вывода до чужой меди не меньше 0.30 мм
    jr_pri = jr_pr;
    if (ml) jr_pri = jr_ceil01(max(jr_pr, 0.30 - jr_cl));

    jr_edge = jr_prof == 0 ? 0.30 : (jr_prof == 1 ? 0.25 : 0.20);
    if (jr_vcut) jr_edge = max(jr_edge, 0.40);
    jr_hh = jr_prof == 0 ? 0.25 : 0.20;
    jr_mask = 0.05;
    jr_vstop = jr_tented ? 0.5 : 0;
    jr_dam = heavy ? 0.20 : 0.10;

    if (jr_snote != "") jr_warn(jr_snote);
    if (jr_thick < 0.6)
        jr_warn(L("Плата тоньше 0.6 мм — JLCPCB проверяет вручную.", "Boards under 0.6 mm are reviewed manually by JLCPCB."));
    if (jr_prof == 2 && ml && !heavy)
        jr_warn(L("Дорожки 0.09 мм (3.5 mil) на многослойной плате: +20 % к цене.", "0.09 mm (3.5 mil) tracks on a multilayer board: +20 % price."));
    if (jr_prof == 2)
        jr_warn(L("Переходные 0.15/0.25 мм: на странице заказа выбрать «Min via hole size» — доплата.",
                  "0.15/0.25 mm vias: choose «Min via hole size» on the order page — extra cost."));
    if (ml && jr_n >= 6)
        jr_warn(L("6+ слоёв: переходные в площадках JLCPCB заливает и закрывает бесплатно (POFV).",
                  "6+ layers: via-in-pad is filled and capped free of charge (POFV)."));
}

// ---------------------------------------------------------------- имена и подписи

// dmxON_JLCPCB_4L_Standard; для нестандартных параметров добавляются суффиксы
string jr_name()
{
    string s = "dmxON_JLCPCB_" + istr(jr_n) + "L";
    if (abs(jr_thick - 1.6) > 0.01) { string t; sprintf(t, "_%.1fmm", jr_thick); s += t; }
    if (jr_oo >= 2) s += "_2oz";
    if (jr_n > 2 && abs(jr_oi - 0.5) > 0.01) s += "_in" + num(jr_oi) + "oz";
    if (jr_vcut) s += "_vcut";
    if (!jr_tented) s += "_open";
    return s + "_" + JR_PID[jr_prof];
}

// «4 layers», «4 слоя», «6 слоёв», «4 warstwy», «6 warstw»
string jr_layers_l(int lg)
{
    string n = istr(jr_n);
    if (lg == 1) return n + (jr_n < 5 ? " слоя" : " слоёв");
    if (lg == 2) return n + " capas";
    if (lg == 3) return n + " Lagen";
    if (lg == 4) return n + (jr_n < 5 ? " warstwy" : " warstw");
    return n + " layers";
}

string jr_setup_string()
{
    string s = "(" + istr(jr_lay[0]);
    for (int i = 0; i < jr_n - 1; i++)
        s += (jr_dk[i] == "C" ? "*" : "+") + istr(jr_lay[i + 1]);
    return s + ")";
}

string jr_layers_txt()
{
    string s = "";
    for (int i = 0; i < jr_n; i++) s += (i ? " " : "") + istr(jr_lay[i]);
    return s;
}

string jr_thick_txt()
{
    string t;
    sprintf(t, "%.1f", jr_thick);
    return t;
}

// одна строка параметров на языке lg (для описания и сводки)
string jr_brief(int lg)
{
    if (jr_n > 2)
        return Lfx(lg, "{0} мм · медь {1} oz / внутри {2} oz", "{0} mm · copper {1} oz / inner {2} oz", jr_thick_txt(), num(jr_oo), num(jr_oi));
    return Lfx(lg, "{0} мм · медь {1} oz", "{0} mm · copper {1} oz", jr_thick_txt(), num(jr_oo), "");
}

string jr_via_txt()
{
    real dia = jr_vd + 2 * max(jr_vr, jr_vd * jr_vrv);
    return num(jr_vd) + "/" + num(round(dia * 1000) / 1000.0);
}

// ---------------------------------------------------------------- файл правил .dru

string jr_dru_text()
{
    string nl = "\n";
    // описание на всех языках: Fusion показывает то, что совпадает с языком его интерфейса
    string desc = "";
    for (int lg = 0; lg < N_LANG; lg++) {
        string d = "<b>" + h("dmxON · JLCPCB " + jr_layers_l(lg) + " · " + jr_pname(lg, jr_prof)) + "</b> (" + h(jr_pnote(lg, jr_prof)) + ")<br>" +
            h(jr_brief(lg) + " · " + Lx(lg, "стек", "stack") + " ") + jr_setup_string() + "<br>" +
            h(Lfx(lg, "Дорожка/зазор {0} мм · переходное {1} мм · до края {2} мм", "Track/space {0} mm · via {1} mm · edge {2} mm",
                  num(jr_tw) + "/" + num(jr_cl), jr_via_txt(), num(jr_edge))) + "<br>" +
            h(JR_NAME + " " + JR_VERSION + " · " + JR_AUTHOR + " " + JR_YEAR);
        desc += "description[" + LANG_CODE[lg] + "] = " + d + nl;
    }

    string cu = "", iso = "";
    for (int l = 1; l <= 16; l++) cu += (l > 1 ? " " : "") + jr_mm((l == 1 || l == 16) ? jr_cuo : jr_cui);
    real iso_v[];
    for (int k = 0; k < 15; k++) iso_v[k] = k == 0 ? 1.5 : (k % 2 ? 0.15 : 0.2);
    for (int i = 0; i < jr_nd; i++) iso_v[jr_lay[i] - 1] = jr_dt[i];
    for (int m = 0; m < 15; m++) iso += (m ? " " : "") + jr_mm(iso_v[m]);

    string vrv;
    sprintf(vrv, "%.6f", jr_vrv);
    string t = "";
    t += desc;
    t += "layerSetup = " + jr_setup_string() + nl;
    t += "mtCopper = " + cu + nl;
    t += "mtIsolate = " + iso + nl;
    t += "mdWireWire = " + jr_mm(jr_cl) + nl;
    t += "mdWirePad = " + jr_mm(jr_cl) + nl;
    t += "mdWireVia = " + jr_mm(jr_cl) + nl;
    t += "mdPadPad = " + jr_mm(jr_smd) + nl;
    t += "mdPadVia = " + jr_mm(jr_cl) + nl;
    t += "mdViaVia = " + jr_mm(jr_cl) + nl;
    // mdSmdPad / mdSmdVia / mdSmdSmd — зазоры внутри ОДНОЙ цепи (в Fusion — «Same Signal»):
    // не больше зазора разных цепей, иначе Fusion предупреждает при загрузке
    t += "mdSmdPad = " + jr_mm(jr_cl) + nl;
    t += "mdSmdVia = " + jr_mm(jr_cl) + nl;
    t += "mdSmdSmd = " + jr_mm(jr_cl) + nl;
    t += "mdViaViaSameLayer = " + jr_mm(jr_cl) + nl;
    t += "mnLayersViaInSmd = 2" + nl;
    t += "mdCopperDimension = " + jr_mm(jr_edge) + nl;
    t += "mdDrill = " + jr_mm(jr_hh) + nl;
    t += "mdSmdStop = 0mil" + nl;
    t += "msWidth = " + jr_mm(jr_tw) + nl;
    t += "msDrill = " + jr_mm(jr_vd) + nl;
    t += "msMicroVia = 9.99mm" + nl;
    t += "msBlindViaRatio = 0.500000" + nl;
    t += "rvPadTop = 0.250000" + nl;
    t += "rvPadInner = 0.250000" + nl;
    t += "rvPadBottom = 0.250000" + nl;
    t += "rvViaOuter = " + vrv + nl;
    t += "rvViaInner = " + vrv + nl;
    t += "rvMicroViaOuter = 0.250000" + nl;
    t += "rvMicroViaInner = 0.250000" + nl;
    t += "rlMinPadTop = " + jr_mm(jr_pr) + nl;
    t += "rlMaxPadTop = 0.5mm" + nl;
    t += "rlMinPadInner = " + jr_mm(jr_pri) + nl;
    t += "rlMaxPadInner = 0.5mm" + nl;
    t += "rlMinPadBottom = " + jr_mm(jr_pr) + nl;
    t += "rlMaxPadBottom = 0.5mm" + nl;
    t += "rlMinViaOuter = " + jr_mm(jr_vr) + nl;
    t += "rlMaxViaOuter = 0.5mm" + nl;
    t += "rlMinViaInner = " + jr_mm(jr_vri) + nl;
    t += "rlMaxViaInner = 0.5mm" + nl;
    t += "rlMinMicroViaOuter = 4mil" + nl;
    t += "rlMaxMicroViaOuter = 20mil" + nl;
    t += "rlMinMicroViaInner = 4mil" + nl;
    t += "rlMaxMicroViaInner = 20mil" + nl;
    t += "psTop = -1" + nl;
    t += "psBottom = -1" + nl;
    t += "psFirst = -1" + nl;
    t += "psElongationLong = 100" + nl;
    t += "psElongationOffset = 100" + nl;
    t += "mvStopFrame = 1.000000" + nl;
    t += "mvCreamFrame = 0.000000" + nl;
    t += "mlMinStopFrame = " + jr_mm(jr_mask) + nl;
    t += "mlMaxStopFrame = " + jr_mm(jr_mask) + nl;
    t += "mlMinCreamFrame = 0mil" + nl;
    t += "mlMaxCreamFrame = 0mil" + nl;
    t += "mlViaStopLimit = " + (jr_vstop > 0 ? jr_mm(jr_vstop) : "0mil") + nl;
    t += "srRoundness = 0.000000" + nl;
    t += "srMinRoundness = 0mil" + nl;
    t += "srMaxRoundness = 0mil" + nl;
    t += "slThermalGap = 0.500000" + nl;
    t += "slMinThermalGap = 20mil" + nl;
    t += "slMaxThermalGap = 100mil" + nl;
    t += "slAnnulusIsolate = 20mil" + nl;
    t += "slThermalIsolate = 10mil" + nl;
    t += "slAnnulusRestring = 0" + nl;
    t += "slThermalRestring = 1" + nl;
    t += "slThermalsForVias = 0" + nl;
    t += "dpMaxLengthDifference = 10mm" + nl;
    t += "dpGapFactor = 2.500000" + nl;
    t += "checkGrid = 0" + nl;
    t += "checkAngle = 0" + nl;
    t += "checkFont = 1" + nl;
    t += "checkRestrict = 1" + nl;
    t += "checkStop = 0" + nl;
    t += "checkValues = 0" + nl;
    t += "checkNames = 1" + nl;
    t += "checkWireStubs = 1" + nl;
    t += "checkPolygonWidth = 0" + nl;
    t += "useDiameter = 13" + nl;
    t += "maxErrors = 1000" + nl;
    return t;
}

int jr_write_dru(string path)
{
    string t = jr_dru_text();
    output(path, "wt") printf("%s", t);
    return file_exists(path);
}

// ---------------------------------------------------------------- задание CAM (Gerber + сверловка с именами JLCPCB)

string jr_q(string s)
{
    return "\"" + s + "\"";
}

// текст для JSON: кириллица -> \uXXXX (файл пишется в однобайтовой кодировке)
string jr_json(string s)
{
    string t = "";
    for (int i = 0; s[i]; i++) {
        int c = s[i];
        if (c == '"') t += "\\\"";
        else if (c == '\\') t += "\\\\";
        else if (c == '\n') t += "\\n";
        else if (c > 126 || c < 0) { string e; sprintf(e, "\\u%04x", c); t += e; }
        else t += s[i];
    }
    return "\"" + t + "\"";
}

string jr_cam_layer(string name, string ext, string layers, string cfg, string extra, int last)
{
    string s = "                {\n";
    s += "                    \"board_outline\": " + (ext == "GKO" ? "true" : "false") + ",\n";
    s += "                    \"config\": {\n" + cfg + "                    },\n";
    s += "                    \"filename_format\": \"%N_%FF." + ext + "\",\n";
    s += "                    \"layers\": [ " + layers + " ],\n";
    s += extra;
    s += "                    \"name\": " + jr_q(name) + ",\n";
    s += "                    \"polarity\": \"positive\",\n";
    s += "                    \"type\": \"gerber_layer\"\n";
    s += "                }" + (last ? "" : ",") + "\n";
    return s;
}

string jr_cfg(string a)
{
    string s = "";
    string p[];
    int n = strsplit(p, a, ';');
    for (int i = 0; i < n; i++) s += "                        " + p[i] + (i < n - 1 ? "," : "") + "\n";
    return s;
}

string jr_cam_text()
{
    string files_en = "", files_ru = "";
    string d_en = "<b>dmxON · JLCPCB " + istr(jr_n) + "-layer CAM job</b><p>Gerber RS-274X + Excellon with JLCPCB file names: GTL";
    for (int g = 1; g <= jr_n - 2; g++) d_en += ", G" + istr(g);
    d_en += ", GBL, GTS, GBS, GTP, GBP, GTO, GBO, GKO, XLN (plated and non-plated holes in one file).<p>Copper layers: " + jr_layers_txt() + ".<p>" +
        JR_NAME + " " + JR_VERSION + " · " + JR_AUTHOR + " " + JR_YEAR;

    string ly = "";
    ly += jr_cam_layer("Board Outline", "GKO", "46, 20",
        jr_cfg("\"file_function\": \"Profile\";\"plating\": \"non-plated\""), "                    \"milling\": true,\n", 0);
    for (int i = 0; i < jr_n; i++) {
        string nm, ext, typ;
        if (i == 0) { nm = "Top Copper"; ext = "GTL"; typ = "top"; }
        else if (i == jr_n - 1) { nm = "Bottom Copper"; ext = "GBL"; typ = "bottom"; }
        else { nm = "Inner Copper Layer " + istr(i); ext = "G" + istr(i); typ = "Inner"; }
        ly += jr_cam_layer(nm, ext, istr(jr_lay[i]) + ", 17, 18",
            jr_cfg("\"file_function\": \"Copper\";\"layer\": " + istr(i + 1) + ";\"layer_details\": \"mixed\";\"layer_type\": \"" + typ + "\""), "", 0);
    }
    ly += jr_cam_layer("Soldermask Top", "GTS", "29", jr_cfg("\"file_function\": \"Soldermask\";\"index\": 1;\"layer_type\": \"top\""), "", 0);
    ly += jr_cam_layer("Soldermask Bottom", "GBS", "30", jr_cfg("\"file_function\": \"Soldermask\";\"index\": 1;\"layer_type\": \"bottom\""), "", 0);
    ly += jr_cam_layer("Solderpaste Top", "GTP", "31", jr_cfg("\"file_function\": \"Paste\";\"layer_type\": \"top\""), "", 0);
    ly += jr_cam_layer("Solderpaste Bottom", "GBP", "32", jr_cfg("\"file_function\": \"Paste\";\"layer_type\": \"bottom\""), "", 0);
    ly += jr_cam_layer("Silkscreen Top", "GTO", "21, 25", jr_cfg("\"file_function\": \"Legend\";\"index\": 1;\"layer_type\": \"top\""), "", 0);
    ly += jr_cam_layer("Silkscreen Bottom", "GBO", "22, 26", jr_cfg("\"file_function\": \"Legend\";\"index\": 1;\"layer_type\": \"bottom\""), "", 1);

    string s = "{\n";
    s += "    \"author\": {\n        \"email\": \"\",\n        \"name\": " + jr_q(JR_AUTHOR) + "\n    },\n";
    s += "    \"description\": {\n        \"EN\": " + jr_json(d_en) + "\n    },\n";
    s += "    \"output_type\": \"directory\",\n";
    s += "    \"outputs\": [\n";
    s += "        {\n";
    s += "            \"filename_prefix\": \"GerberJob\",\n";
    s += "            \"format_specifier\": {\n                \"decimal\": 4,\n                \"integer\": 3\n            },\n";
    s += "            \"generate_job_file\": true,\n";
    s += "            \"output_type\": \"gerber\",\n";
    s += "            \"outputs\": [\n" + ly + "            ],\n";
    s += "            \"version\": \"RS274X\"\n";
    s += "        },\n";
    s += "        {\n";
    s += "            \"filename_prefix\": \"\",\n";
    s += "            \"format_specifier\": {\n                \"decimal\": 3,\n                \"integer\": 3\n            },\n";
    s += "            \"output_type\": \"drill\",\n";
    s += "            \"outputs\": [\n";
    s += "                {\n";
    s += "                    \"drills\": {\n                        \"NPTH\": true,\n                        \"PTH\": true,\n                        \"VIA\": true\n                    },\n";
    s += "                    \"filename_format\": \"%N_drill.XLN\",\n";
    s += "                    \"layers\": {\n                        \"from\": 1,\n                        \"to\": 16\n                    },\n";
    s += "                    \"name\": \"Drill File\",\n";
    s += "                    \"type\": \"excellon\"\n";
    s += "                }\n";
    s += "            ]\n";
    s += "        }\n";
    s += "    ],\n";
    s += "    \"timestamp\": \"" + JR_DATE + "T00:00:00\",\n";
    s += "    \"type\": \"EAGLE CAM job\",\n";
    s += "    \"units\": \"metric\",\n";
    s += "    \"version\": \"9.2.0\"\n";
    s += "}\n";
    return s;
}

string jr_cam_name()
{
    string s = "dmxON_JLCPCB_" + istr(jr_n) + "L";
    string def = jr_layers_txt();
    int keep[];
    for (int i = 0; i < jr_n; i++) keep[i] = jr_lay[i];
    jr_default_layers();
    if (jr_layers_txt() != def) s += "_L" + replace_all(def, " ", "-");
    for (int j = 0; j < jr_n; j++) jr_lay[j] = keep[j];
    return s;
}

int jr_write_cam(string path)
{
    string t = jr_cam_text();
    output(path, "wt") printf("%s", t);
    return file_exists(path);
}

// ---------------------------------------------------------------- готовый пакет: 4 × 3 файла правил + 4 задания CAM

int jr_write_pack(string dir, string dir_cam)
{
    int n_ok = 0;
    int keep_n = jr_n, keep_p = jr_prof, keep_t = jr_tented, keep_v = jr_vcut;
    real keep_th = jr_thick, keep_oo = jr_oo, keep_oi = jr_oi;
    int keep_lay[];
    for (int k = 0; k < 16; k++) keep_lay[k] = jr_lay[k];
    for (int n = 2; n <= 8; n += 2) {
        jr_n = n; jr_thick = 1.6; jr_oo = 1; jr_oi = 0.5; jr_tented = 1; jr_vcut = 0;
        jr_default_layers();
        for (int p = 0; p < 3; p++) {
            jr_prof = p;
            jr_calc();
            if (jr_write_dru(dir + "/" + jr_name() + ".dru")) n_ok++;
        }
        if (jr_write_cam(dir_cam + "/" + jr_cam_name() + ".cam")) n_ok++;
    }
    jr_n = keep_n; jr_prof = keep_p; jr_tented = keep_t; jr_vcut = keep_v;
    jr_thick = keep_th; jr_oo = keep_oo; jr_oi = keep_oi;
    for (int j = 0; j < 16; j++) jr_lay[j] = keep_lay[j];
    return n_ok;
}
