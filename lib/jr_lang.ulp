// jr_lang.ulp — переводы интерфейса: испанский, немецкий, польский (русский и английский — в коде)
// dmxON JLC Rules · dmxON by AlexSmith 2026 · см. LICENSE.md
// Создаётся из lang/strings.tsv (ключ — английский текст); правьте TSV, не этот файл.

string TR_EN[] = {
    "0.09 mm (3.5 mil) tracks on a multilayer board: +20 % price.",
    "0.15/0.25 mm vias: choose «Min via hole size» on the order page — extra cost.",
    "6+ layers: via-in-pad is filled and capped free of charge (POFV).",
    "above the allowed maximum",
    "Actions",
    "acute angle",
    "Already installed — «Install» updates the files.",
    "Apply",
    "approved",
    "approved DRC",
    "blind via",
    "Board",
    "Board check",
    "board line",
    "board shape",
    "board stack-up",
    "Board {0} mm exceeds {1} mm.",
    "Boards under 0.6 mm are reviewed manually by JLCPCB.",
    "CAM job",
    "Cancel",
    "Cannot copy the files to:",
    "Cannot find the user folder.",
    "Cannot install the dmxON add-in to:",
    "Cannot write the rules file:",
    "circle",
    "clearance between nets",
    "computed",
    "copper",
    "copper in a restricted area",
    "Copper layers",
    "copper on layers",
    "copper too close to the board edge",
    "core",
    "dam",
    "Dense",
    "detected",
    "different nets overlap",
    "dmxON JLC Rules removed.",
    "Done.",
    "Dot grid: board 1 / 0.1 mm, schematic 0.1″",
    "Dot grid: board 1 mm (alternate 0.1 mm)",
    "drill below the minimum",
    "Drills below {0} mm: holes under 0.3 mm cost extra at JLCPCB — enlarge them or choose the Extreme profile.",
    "edge",
    "Edge / hole gap",
    "Error list — ERRORS panel; rules — DRC command.",
    "Errors",
    "Extreme",
    "files",
    "Files only…",
    "Folder for the rule files",
    "Fusion reported no DRC result — open DRC manually.",
    "GOST R 53429-2009: accuracy class {0} (track and space ≥ {1} mm)",
    "graphics of {0}",
    "holes too close together",
    "inner",
    "Inner copper",
    "Inner copper {0} oz is not offered for this stack-up — using {1} oz.",
    "Install",
    "Installation",
    "Installation into Autodesk Fusion:",
    "invalid polygon",
    "IPC-2221C — design · IPC-6012F Class 2 — fabrication · IPC-A-600M — acceptance",
    "JLCPCB board setup",
    "JLCPCB minimum, may cost extra",
    "JLCPCB setup summary",
    "keep-out area",
    "Language",
    "Layer {0} is outside the {1}-layer stack-up but holds: {2}. Move it off the layer or choose more layers.",
    "length matching",
    "loaded into the board",
    "Mask",
    "Mask colour",
    "micro via",
    "mm",
    "more than 8 layers — the pack covers up to 8",
    "narrow gap in copper",
    "Net class {0} «{1}» is below the JLCPCB minimum.",
    "Net classes not below the minimum",
    "Net classes raised to the minimum",
    "No board outline (layer 20 Dimension).",
    "No errors",
    "No findings.",
    "no objects found — Fusion marks the layer as used, check it by hand",
    "no-extra-cost limits",
    "Non-plated holes below 0.5 mm: {0} (smallest {1}) — JLCPCB minimum is 0.5.",
    "object on a wrong layer",
    "off grid",
    "Outer copper",
    "pad of {0}",
    "pad to pad",
    "parts in each other's keep-out",
    "pour {0}",
    "prepreg",
    "Previous rules saved",
    "Profile",
    "PTH ring",
    "rectangle",
    "Remove",
    "Restart Fusion once after installing.",
    "Restart Fusion to remove the dmxON tab.",
    "Restart Fusion — the dmxON tab appears in the PCB and schematic editors, and {0} in Automation → Run ULP.",
    "Restore previous rules",
    "ring",
    "Rule pack",
    "Rule pack and CAM into the rules folder",
    "Rule pack written",
    "Run from the board editor (or with -export <folder> for the rule pack only).",
    "schematic 0.1″ (alternate 0.025″)",
    "schematic: the dmxON add-in is not running — in the schematic run",
    "Silkscreen lines thinner than 0.15 mm: {0} (thinnest {1}) — will print thin or broken.",
    "silkscreen near exposed copper",
    "Silkscreen texts below 1.0 mm: {0} (smallest {1}) — may be unreadable.",
    "SMD pad size",
    "solder mask",
    "Stack",
    "stack",
    "Stack-up",
    "Standard",
    "Standards",
    "Tented vias",
    "text not in vector font",
    "text «{0}»",
    "Texts with strokes under 0.15 mm: {0} — increase the font ratio.",
    "The board has {0} approved DRC messages. A check with the new rules drops approvals that no longer match — «Restore» cannot bring them back. Save a board version first.",
    "The board is smaller than 3 × 3 mm — not manufacturable at JLCPCB.",
    "the dmxON add-in is installed: the <b>dmxON</b> tab appears in the PCB and schematic editors — FabKit, JLC Rules, backup of the design folder, updates from GitHub",
    "The dmxON add-in is updated — restart Fusion to run the new version.",
    "the dmxON folders are added to Fusion's ULP, design rules and CAM lists — <b>{0}</b> is also in Automation → Run ULP; the built-in ULPs stay",
    "The dmxON tab is already running and {0} is updated — it is also in Automation → Run ULP.",
    "the project is copied to <tt>{0}</tt>",
    "The setup is free. If it helped, support new versions",
    "Thickness and mask to dmxON FabKit",
    "Thickness, mm",
    "To restore the previous rules: run the setup again and press «Restore previous rules».",
    "Track / space",
    "track {0}",
    "track/space",
    "Track/space {0} mm · via {1} mm · edge {2} mm",
    "track/space/drill, mm",
    "Tracks thinner than {0} mm: {1} (thinnest {2}) — DRC will flag them.",
    "unrouted connections",
    "V-cut panel: copper 0.4 mm from edge",
    "Via",
    "via",
    "via in a restricted area",
    "via {0}",
    "Vias below 0.3 mm: {0} — small-hole surcharge.",
    "Vias drilled below {0} mm: {1} (smallest {2}).",
    "vias open",
    "vias ≤ 0.5 tented",
    "warnings",
    "width below the minimum",
    "wire stub",
    "with margin, no extra cost",
    "Written",
    "{0} mm is not offered for {1} layers — using {2} mm.",
    "{0} mm · copper {1} oz",
    "{0} mm · copper {1} oz / inner {2} oz"
};

string TR_ES[] = {
    "Pistas de 0.09 mm (3.5 mil) en una placa multicapa: +20 % al precio.",
    "Vías de 0.15/0.25 mm: elija «Min via hole size» en la página del pedido — coste adicional.",
    "6+ capas: las vías en pad se rellenan y tapan gratis (POFV).",
    "por encima del máximo permitido",
    "Acciones",
    "ángulo agudo",
    "Ya instalado — «Instalar» actualiza los archivos.",
    "Aplicar",
    "aprobados",
    "DRC aprobados",
    "vía ciega",
    "Placa",
    "Comprobación de la placa",
    "línea en la placa",
    "forma en la placa",
    "apilado de la placa",
    "La placa de {0} mm supera {1} mm.",
    "JLCPCB revisa manualmente las placas de menos de 0.6 mm.",
    "trabajo CAM",
    "Cancelar",
    "No se pueden copiar los archivos a:",
    "No se encuentra la carpeta del usuario.",
    "No se pudo instalar el complemento dmxON en:",
    "No se puede escribir el archivo de reglas:",
    "círculo",
    "separación entre redes",
    "calculado",
    "cobre",
    "cobre en zona restringida",
    "Capas de cobre",
    "cobre en capas",
    "cobre demasiado cerca del borde",
    "núcleo",
    "puente de máscara",
    "Denso",
    "detectado",
    "solape de redes distintas",
    "dmxON JLC Rules eliminado.",
    "Hecho.",
    "Rejilla de puntos: placa 1 / 0,1 mm, esquema 0,1″",
    "Rejilla de puntos: placa 1 mm (alternativa 0,1 mm)",
    "taladro por debajo del mínimo",
    "Taladros de menos de {0} mm: en JLCPCB los agujeros de menos de 0.3 mm tienen recargo — agrándelos o elija el perfil Extremo.",
    "borde",
    "Borde / entre agujeros",
    "Lista de errores — panel ERRORS; reglas — comando DRC.",
    "Errores",
    "Extremo",
    "archivos",
    "Solo archivos…",
    "Carpeta para los archivos de reglas",
    "Fusion no devolvió el resultado del DRC — ábralo manualmente.",
    "GOST R 53429-2009: clase de precisión {0} (pista y separación ≥ {1} mm)",
    "gráficos de {0}",
    "agujeros demasiado juntos",
    "interior",
    "Cobre interior",
    "JLCPCB no ofrece cobre interior de {0} oz para este apilado — se usa {1} oz.",
    "Instalar",
    "Instalación",
    "Instalación en Autodesk Fusion:",
    "polígono no válido",
    "IPC-2221C — diseño · IPC-6012F clase 2 — fabricación · IPC-A-600M — aceptación",
    "Configuración de la placa para JLCPCB",
    "mínimo de JLCPCB, puede tener recargo",
    "Resumen de la configuración JLCPCB",
    "zona de exclusión",
    "Idioma",
    "La capa {0} está fuera del apilado de {1} capas, pero contiene: {2}. Quítelo de la capa o elija más capas.",
    "igualación de longitudes",
    "cargadas en la placa",
    "Máscara",
    "Color de máscara",
    "microvía",
    "mm",
    "más de 8 capas — el paquete cubre hasta 8",
    "hueco estrecho en el cobre",
    "La clase de red {0} «{1}» está por debajo del mínimo de JLCPCB.",
    "Clases de red no por debajo del mínimo",
    "Clases de red elevadas al mínimo",
    "No hay contorno de placa (capa 20 Dimension).",
    "Sin errores",
    "Sin observaciones.",
    "no se encontraron objetos — Fusion marca la capa como usada, revísela a mano",
    "límites sin recargo",
    "Agujeros no metalizados de menos de 0.5 mm: {0} (el menor {1}) — el mínimo de JLCPCB es 0.5.",
    "objeto en una capa incorrecta",
    "fuera de la rejilla",
    "Cobre exterior",
    "pad de {0}",
    "pad a pad",
    "componentes en la zona de exclusión de otros",
    "relleno {0}",
    "preimpregnado",
    "Reglas anteriores guardadas",
    "Perfil",
    "Anillo PTH",
    "rectángulo",
    "Quitar",
    "Tras instalar, reinicie Fusion una vez.",
    "Reinicie Fusion para quitar la pestaña dmxON.",
    "Reinicie Fusion: la pestaña dmxON aparece en los editores de placa y esquema, y {0} en Automation → Run ULP.",
    "Restaurar reglas anteriores",
    "anillo",
    "Paquete de reglas",
    "Paquete de reglas y CAM en la carpeta de reglas",
    "Paquete de reglas guardado",
    "Ejecútelo desde el editor de placa (o con -export <carpeta> solo para el paquete de reglas).",
    "esquema 0,1″ (alternativa 0,025″)",
    "esquema: el complemento dmxON no está en ejecución; en el esquema ejecute",
    "Líneas de serigrafía de menos de 0.15 mm: {0} (la más fina {1}) — se imprimirán finas o cortadas.",
    "serigrafía junto a cobre expuesto",
    "Textos de serigrafía de menos de 1.0 mm: {0} (el menor {1}) — pueden no leerse.",
    "tamaño de pad SMD",
    "máscara de soldadura",
    "Apilado",
    "apilado",
    "Apilado de capas",
    "Estándar",
    "Normas",
    "Vías cubiertas",
    "texto sin fuente vectorial",
    "texto «{0}»",
    "Textos con trazo de menos de 0.15 mm: {0} — aumente el ratio de la fuente.",
    "La placa tiene {0} mensajes DRC aprobados. Una comprobación con las reglas nuevas elimina las aprobaciones que ya no coincidan — «Restaurar» no las recupera. Guarde antes una versión de la placa.",
    "La placa es menor de 3 × 3 mm — JLCPCB no la fabrica.",
    "se instala el complemento dmxON: la pestaña <b>dmxON</b> aparece en los editores de placa y esquema — FabKit, JLC Rules, copia de la carpeta del diseño, actualizaciones desde GitHub",
    "El complemento dmxON se actualizó: reinicie Fusion para usar la nueva versión.",
    "las carpetas dmxON se añaden a las listas de ULP, reglas de diseño y CAM de Fusion — <b>{0}</b> también está en Automation → Run ULP; los ULP integrados se mantienen",
    "La pestaña dmxON ya funciona y {0} está actualizado; también está en Automation → Run ULP.",
    "el proyecto se copia en <tt>{0}</tt>",
    "La herramienta es gratuita. Si le ayudó, apoye nuevas versiones",
    "Espesor y máscara a dmxON FabKit",
    "Espesor, mm",
    "Para restaurar las reglas anteriores: ejecute la herramienta de nuevo y pulse «Restaurar reglas anteriores».",
    "Pista / separación",
    "pista {0}",
    "pista/separación",
    "Pista/separación {0} mm · vía {1} mm · borde {2} mm",
    "pista/separación/taladro, mm",
    "Pistas de menos de {0} mm: {1} (la más fina {2}) — el DRC las marcará.",
    "conexiones sin rutear",
    "Panel V-cut: cobre a 0.4 mm del borde",
    "Vía",
    "vía",
    "vía en zona restringida",
    "vía {0}",
    "Vías de menos de 0.3 mm: {0} — recargo por agujeros pequeños.",
    "Vías con taladro de menos de {0} mm: {1} (la menor {2}).",
    "vías descubiertas",
    "vías ≤ 0.5 cubiertas",
    "advertencias",
    "ancho por debajo del mínimo",
    "trozo de pista suelto",
    "con margen, sin recargo",
    "Guardado",
    "JLCPCB no ofrece {0} mm para {1} capas — se usa {2} mm.",
    "{0} mm · cobre {1} oz",
    "{0} mm · cobre {1} oz / interior {2} oz"
};

string TR_DE[] = {
    "Leiterbahnen 0.09 mm (3.5 mil) auf einer Mehrlagenplatine: +20 % Aufpreis.",
    "Vias 0.15/0.25 mm: auf der Bestellseite «Min via hole size» wählen — Aufpreis.",
    "Ab 6 Lagen: Via-in-Pad wird kostenlos gefüllt und abgedeckt (POFV).",
    "über dem zulässigen Maximum",
    "Aktionen",
    "spitzer Winkel",
    "Bereits installiert — «Installieren» aktualisiert die Dateien.",
    "Anwenden",
    "genehmigt",
    "DRC genehmigt",
    "Blind Via",
    "Platine",
    "Platinenprüfung",
    "Linie auf der Platine",
    "Form auf der Platine",
    "Lagenaufbau der Platine",
    "Platine {0} mm überschreitet {1} mm.",
    "Platinen unter 0.6 mm prüft JLCPCB manuell.",
    "CAM-Job",
    "Abbrechen",
    "Dateien können nicht kopiert werden nach:",
    "Benutzerordner nicht gefunden.",
    "Das dmxON-Add-in konnte nicht installiert werden in:",
    "Regeldatei kann nicht geschrieben werden:",
    "Kreis",
    "Abstand zwischen Netzen",
    "berechnet",
    "Kupfer",
    "Kupfer in Sperrfläche",
    "Kupferlagen",
    "Kupfer auf Lagen",
    "Kupfer zu nah am Platinenrand",
    "Kern",
    "Lötstoppsteg",
    "Dicht",
    "erkannt",
    "Überlappung verschiedener Netze",
    "dmxON JLC Rules entfernt.",
    "Fertig.",
    "Punktraster: Platine 1 / 0,1 mm, Schaltplan 0,1″",
    "Punktraster: Platine 1 mm (alternativ 0,1 mm)",
    "Bohrung unter dem Minimum",
    "Bohrungen unter {0} mm: Löcher unter 0.3 mm kosten bei JLCPCB Aufpreis — vergrößern oder Profil Extrem wählen.",
    "Rand",
    "Rand / Lochabstand",
    "Fehlerliste — Bereich ERRORS; Regeln — Befehl DRC.",
    "Fehler",
    "Extrem",
    "Dateien",
    "Nur Dateien…",
    "Ordner für die Regeldateien",
    "Fusion hat kein DRC-Ergebnis gemeldet — DRC manuell öffnen.",
    "GOST R 53429-2009: Genauigkeitsklasse {0} (Leiterbahn und Abstand ≥ {1} mm)",
    "Grafik von {0}",
    "Löcher zu dicht beieinander",
    "innen",
    "Kupfer innen",
    "Innenkupfer {0} oz gibt es für diesen Aufbau nicht — verwendet wird {1} oz.",
    "Installieren",
    "Installation",
    "Installation in Autodesk Fusion:",
    "ungültiges Polygon",
    "IPC-2221C — Entwurf · IPC-6012F Klasse 2 — Fertigung · IPC-A-600M — Abnahme",
    "Platinen-Einrichtung für JLCPCB",
    "JLCPCB-Minimum, ggf. Aufpreis",
    "Zusammenfassung der JLCPCB-Einrichtung",
    "Sperrfläche",
    "Sprache",
    "Lage {0} liegt außerhalb des Aufbaus mit {1} Lagen, enthält aber: {2}. Entfernen Sie es von der Lage oder wählen Sie mehr Lagen.",
    "Längenabgleich",
    "in die Platine geladen",
    "Lötstopp",
    "Lötstoppfarbe",
    "Microvia",
    "mm",
    "mehr als 8 Lagen — das Paket deckt bis 8 ab",
    "schmaler Spalt im Kupfer",
    "Netzklasse {0} «{1}» liegt unter dem JLCPCB-Minimum.",
    "Netzklassen nicht unter dem Minimum",
    "Netzklassen auf das Minimum angehoben",
    "Keine Platinenkontur (Lage 20 Dimension).",
    "Keine Fehler",
    "Keine Befunde.",
    "keine Objekte gefunden — Fusion markiert die Lage als belegt, bitte manuell prüfen",
    "Grenzen ohne Aufpreis",
    "Nicht durchkontaktierte Löcher unter 0.5 mm: {0} (kleinstes {1}) — JLCPCB-Minimum ist 0.5.",
    "Objekt auf falscher Lage",
    "außerhalb des Rasters",
    "Kupfer außen",
    "Pad von {0}",
    "Pad zu Pad",
    "Bauteile in fremder Sperrfläche",
    "Fläche {0}",
    "Prepreg",
    "Bisherige Regeln gesichert",
    "Profil",
    "Restring THT",
    "Rechteck",
    "Entfernen",
    "Nach der Installation Fusion einmal neu starten.",
    "Fusion neu starten, um den Reiter dmxON zu entfernen.",
    "Fusion neu starten — der Reiter dmxON erscheint im Platinen- und Schaltplan-Editor, {0} unter Automation → Run ULP.",
    "Bisherige Regeln wiederherstellen",
    "Restring",
    "Regelpaket",
    "Regelpaket und CAM in den Regelordner",
    "Regelpaket geschrieben",
    "Im Board-Editor starten (oder mit -export <Ordner> nur für das Regelpaket).",
    "Schaltplan 0,1″ (alternativ 0,025″)",
    "Schaltplan: Das dmxON-Add-in läuft nicht — im Schaltplan ausführen:",
    "Bestückungsdrucklinien dünner als 0.15 mm: {0} (dünnste {1}) — werden dünn oder lückenhaft gedruckt.",
    "Bestückungsdruck an offenem Kupfer",
    "Bestückungsdrucktexte unter 1.0 mm: {0} (kleinster {1}) — evtl. unleserlich.",
    "SMD-Padgröße",
    "Lötstoppmaske",
    "Aufbau",
    "Aufbau",
    "Lagenaufbau",
    "Standard",
    "Normen",
    "Abgedeckte Vias",
    "Text nicht in Vektorschrift",
    "Text «{0}»",
    "Texte mit Strichstärke unter 0.15 mm: {0} — Ratio der Schrift erhöhen.",
    "Die Platine hat {0} genehmigte DRC-Meldungen. Eine Prüfung mit den neuen Regeln entfernt Genehmigungen, die nicht mehr passen — «Wiederherstellen» bringt sie nicht zurück. Speichern Sie vorher eine Version der Platine.",
    "Die Platine ist kleiner als 3 × 3 mm — bei JLCPCB nicht fertigbar.",
    "das dmxON-Add-in wird installiert: Der Reiter <b>dmxON</b> erscheint im Platinen- und Schaltplan-Editor — FabKit, JLC Rules, Sicherung des Designordners, Updates von GitHub",
    "Das dmxON-Add-in wurde aktualisiert — Fusion neu starten, um die neue Version zu nutzen.",
    "die dmxON-Ordner werden zu den ULP-, Designregel- und CAM-Listen von Fusion hinzugefügt — <b>{0}</b> steht auch unter Automation → Run ULP; die eingebauten ULPs bleiben",
    "Der Reiter dmxON läuft bereits und {0} ist aktualisiert — es steht auch unter Automation → Run ULP.",
    "das Projekt wird nach <tt>{0}</tt> kopiert",
    "Das Werkzeug ist kostenlos. Wenn es geholfen hat, unterstützen Sie neue Versionen",
    "Dicke und Lötstopp an dmxON FabKit",
    "Dicke, mm",
    "Bisherige Regeln wiederherstellen: Werkzeug erneut starten und «Bisherige Regeln wiederherstellen» drücken.",
    "Leiterbahn / Abstand",
    "Leiterbahn {0}",
    "Bahn/Abstand",
    "Bahn/Abstand {0} mm · Via {1} mm · Rand {2} mm",
    "Bahn/Abstand/Bohrung, mm",
    "Leiterbahnen dünner als {0} mm: {1} (dünnste {2}) — der DRC wird sie melden.",
    "unverlegte Verbindungen",
    "V-Cut-Nutzen: Kupfer 0.4 mm vom Rand",
    "Via",
    "Via",
    "Via in Sperrfläche",
    "Via {0}",
    "Vias unter 0.3 mm: {0} — Aufpreis für kleine Löcher.",
    "Vias mit Bohrung unter {0} mm: {1} (kleinste {2}).",
    "Vias offen",
    "Vias ≤ 0.5 abgedeckt",
    "Warnungen",
    "Breite unter dem Minimum",
    "Leiterbahnstummel",
    "mit Reserve, ohne Aufpreis",
    "Geschrieben",
    "{0} mm gibt es für {1} Lagen nicht — verwendet wird {2} mm.",
    "{0} mm · Kupfer {1} oz",
    "{0} mm · Kupfer {1} oz / innen {2} oz"
};

string TR_PL[] = {
    "Ścieżki 0.09 mm (3.5 mil) na płytce wielowarstwowej: +20 % do ceny.",
    "Przelotki 0.15/0.25 mm: wybierz «Min via hole size» na stronie zamówienia — dopłata.",
    "6+ warstw: przelotki w padach są wypełniane i zakrywane bezpłatnie (POFV).",
    "powyżej dopuszczalnego maksimum",
    "Działania",
    "kąt ostry",
    "Już zainstalowano — «Zainstaluj» zaktualizuje pliki.",
    "Zastosuj",
    "zatwierdzone",
    "zatwierdzone DRC",
    "przelotka ślepa",
    "Płytka",
    "Kontrola płytki",
    "linia na płytce",
    "kształt na płytce",
    "stos warstw płytki",
    "Płytka {0} mm przekracza {1} mm.",
    "Płytki cieńsze niż 0.6 mm JLCPCB sprawdza ręcznie.",
    "zadanie CAM",
    "Anuluj",
    "Nie można skopiować plików do:",
    "Nie znaleziono folderu użytkownika.",
    "Nie udało się zainstalować dodatku dmxON w:",
    "Nie można zapisać pliku reguł:",
    "okrąg",
    "odstęp między sieciami",
    "obliczono",
    "miedź",
    "miedź w strefie zabronionej",
    "Warstwy miedzi",
    "miedź na warstwach",
    "miedź za blisko krawędzi płytki",
    "rdzeń",
    "mostek maski",
    "Gęsty",
    "wykryto",
    "nakładanie się różnych sieci",
    "dmxON JLC Rules usunięty.",
    "Gotowe.",
    "Siatka punktowa: płytka 1 / 0,1 mm, schemat 0,1″",
    "Siatka punktowa: płytka 1 mm (alternatywna 0,1 mm)",
    "wiercenie poniżej minimum",
    "Wiercenia poniżej {0} mm: otwory mniejsze niż 0.3 mm są w JLCPCB dodatkowo płatne — powiększ je lub wybierz profil Ekstremalny.",
    "krawędź",
    "Krawędź / odstęp otworów",
    "Lista błędów — panel ERRORS; reguły — polecenie DRC.",
    "Błędy",
    "Ekstremalny",
    "plików",
    "Tylko pliki…",
    "Folder na pliki reguł",
    "Fusion nie zwrócił wyniku DRC — otwórz DRC ręcznie.",
    "GOST R 53429-2009: klasa dokładności {0} (ścieżka i odstęp ≥ {1} mm)",
    "grafika {0}",
    "otwory zbyt blisko siebie",
    "wewnątrz",
    "Miedź wewnętrzna",
    "Miedź wewnętrzna {0} oz nie jest dostępna dla tego stosu — użyto {1} oz.",
    "Zainstaluj",
    "Instalacja",
    "Instalacja w Autodesk Fusion:",
    "nieprawidłowy wielokąt",
    "IPC-2221C — projektowanie · IPC-6012F klasa 2 — produkcja · IPC-A-600M — odbiór",
    "Konfiguracja płytki pod JLCPCB",
    "minimum JLCPCB, możliwa dopłata",
    "Podsumowanie konfiguracji JLCPCB",
    "strefa wykluczenia",
    "Język",
    "Warstwa {0} jest poza stosem {1} warstw, a zawiera: {2}. Usuń to z warstwy lub wybierz więcej warstw.",
    "wyrównanie długości",
    "wczytane do płytki",
    "Maska",
    "Kolor maski",
    "mikroprzelotka",
    "mm",
    "ponad 8 warstw — pakiet obejmuje do 8",
    "wąska szczelina w miedzi",
    "Klasa sieci {0} «{1}» jest poniżej minimum JLCPCB.",
    "Klasy sieci nie poniżej minimum",
    "Klasy sieci podniesione do minimum",
    "Brak obrysu płytki (warstwa 20 Dimension).",
    "Brak błędów",
    "Brak uwag.",
    "nie znaleziono obiektów — Fusion oznacza warstwę jako zajętą, sprawdź ją ręcznie",
    "granice bez dopłat",
    "Otwory niemetalizowane poniżej 0.5 mm: {0} (najmniejszy {1}) — minimum JLCPCB to 0.5.",
    "obiekt na niewłaściwej warstwie",
    "poza siatką",
    "Miedź zewnętrzna",
    "pad {0}",
    "pad–pad",
    "elementy w strefie wykluczenia innych",
    "wylewka {0}",
    "prepreg",
    "Poprzednie reguły zapisane",
    "Profil",
    "Pierścień PTH",
    "prostokąt",
    "Usuń",
    "Po instalacji uruchom ponownie Fusion jeden raz.",
    "Uruchom ponownie Fusion, aby usunąć kartę dmxON.",
    "Uruchom ponownie Fusion — karta dmxON pojawi się w edytorach płytki i schematu, a {0} w Automation → Run ULP.",
    "Przywróć poprzednie reguły",
    "pierścień",
    "Pakiet reguł",
    "Pakiet reguł i CAM do folderu reguł",
    "Pakiet reguł zapisany",
    "Uruchom w edytorze płytki (lub z -export <folder> tylko dla pakietu reguł).",
    "schemat 0,1″ (alternatywna 0,025″)",
    "schemat: dodatek dmxON nie działa — w schemacie wykonaj",
    "Linie opisu cieńsze niż 0.15 mm: {0} (najcieńsza {1}) — wydrukują się cienko lub z przerwami.",
    "opis przy odsłoniętej miedzi",
    "Napisy opisu mniejsze niż 1.0 mm: {0} (najmniejszy {1}) — mogą być nieczytelne.",
    "rozmiar pada SMD",
    "maska lutownicza",
    "Stos",
    "stos",
    "Stos warstw",
    "Standard",
    "Normy",
    "Przelotki pod maską",
    "tekst nie czcionką wektorową",
    "tekst «{0}»",
    "Napisy z kreską cieńszą niż 0.15 mm: {0} — zwiększ ratio czcionki.",
    "Płytka ma {0} zatwierdzonych komunikatów DRC. Kontrola z nowymi regułami usunie zatwierdzenia, które przestaną pasować — «Przywróć» ich nie odzyska. Najpierw zapisz wersję płytki.",
    "Płytka jest mniejsza niż 3 × 3 mm — JLCPCB jej nie wykona.",
    "instalowany jest dodatek dmxON: w edytorach płytki i schematu pojawia się karta <b>dmxON</b> — FabKit, JLC Rules, kopia folderu projektu, aktualizacje z GitHuba",
    "Dodatek dmxON zaktualizowano — uruchom ponownie Fusion, aby działała nowa wersja.",
    "foldery dmxON są dodawane do list ULP, reguł projektowych i CAM w Fusion — <b>{0}</b> jest też w Automation → Run ULP; wbudowane ULP pozostają",
    "Karta dmxON już działa, a {0} jest zaktualizowany — jest też w Automation → Run ULP.",
    "projekt zostaje skopiowany do <tt>{0}</tt>",
    "Narzędzie jest bezpłatne. Jeśli pomogło, wesprzyj nowe wersje",
    "Grubość i maska do dmxON FabKit",
    "Grubość, mm",
    "Aby przywrócić poprzednie reguły: uruchom narzędzie ponownie i naciśnij «Przywróć poprzednie reguły».",
    "Ścieżka / odstęp",
    "ścieżka {0}",
    "ścieżka/odstęp",
    "Ścieżka/odstęp {0} mm · przelotka {1} mm · krawędź {2} mm",
    "ścieżka/odstęp/wiercenie, mm",
    "Ścieżki cieńsze niż {0} mm: {1} (najcieńsza {2}) — DRC je zgłosi.",
    "niepoprowadzone połączenia",
    "Panel V-cut: miedź 0.4 mm od krawędzi",
    "Przelotka",
    "przelotka",
    "przelotka w strefie zabronionej",
    "przelotka {0}",
    "Przelotki poniżej 0.3 mm: {0} — dopłata za małe otwory.",
    "Przelotki z wierceniem poniżej {0} mm: {1} (najmniejsza {2}).",
    "przelotki odkryte",
    "przelotki ≤ 0.5 pod maską",
    "ostrzeżenia",
    "szerokość poniżej minimum",
    "urwana ścieżka",
    "z zapasem, bez dopłat",
    "Zapisano",
    "{0} mm nie jest dostępne dla {1} warstw — użyto {2} mm.",
    "{0} mm · miedź {1} oz",
    "{0} mm · miedź {1} oz / wewnątrz {2} oz"
};

int TR_N = 159;
