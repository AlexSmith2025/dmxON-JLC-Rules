// jr_stack.ulp — стеки слоёв JLCPCB (шаблоны «No requirement» со страницы заказа)
// dmxON JLC Rules · dmxON by AlexSmith 2026 · см. LICENSE.md
//
// Строка: слои|толщина, мм|медь снаружи, oz|медь внутри, oz|медь снаружи, мм|медь внутри, мм|
// диэлектрики сверху вниз: P — препрег, C — ядро; толщина:ткань:Er
// Row: layers|thickness mm|outer oz|inner oz|outer mm|inner mm|dielectrics top to bottom
// (P prepreg, C core; thickness:glass:Er). Generated from JLCPCB stack-up data.

string JR_STACK[] = {
    "4|0.8|1|0.5|0.035|0.0152|P0.2104:7628:4.40 C0.25:core:4.23 P0.2104:7628:4.40",
    "4|0.8|1|1|0.035|0.03|P0.203:7628:4.40 C0.25:core:4.23 P0.203:7628:4.40",
    "4|0.8|1|2|0.035|0.061|P0.1605:3313+1080:4.10 C0.3:core:4.41 P0.1605:1080+3313:4.10",
    "4|0.8|2|0.5|0.07|0.0152|P0.2104:7628:4.40 C0.2:core:4.36 P0.2104:7628:4.40",
    "4|0.8|2|1|0.07|0.03|P0.203:7628:4.40 C0.2:core:4.36 P0.203:7628:4.40",
    "4|0.8|2|2|0.07|0.061|P0.1835:3313+3313:4.10 C0.15:core:4.36 P0.1835:3313+3313:4.10",
    "4|1|1|0.5|0.035|0.0152|P0.2104:7628:4.40 C0.5:core:4.48 P0.2104:7628:4.40",
    "4|1|1|1|0.035|0.03|P0.203:7628:4.40 C0.45:core:4.36 P0.203:7628:4.40",
    "4|1|1|2|0.035|0.061|P0.1605:3313+1080:4.10 C0.5:core:4.48 P0.1605:1080+3313:4.10",
    "4|1|2|0.5|0.07|0.0152|P0.2104:7628:4.40 C0.4:core:4.36 P0.2104:7628:4.40",
    "4|1|2|1|0.07|0.03|P0.203:7628:4.40 C0.4:core:4.36 P0.203:7628:4.40",
    "4|1|2|2|0.07|0.061|P0.1835:3313+3313:4.10 C0.35:core:4.36 P0.1835:3313+3313:4.10",
    "4|1.2|1|0.5|0.035|0.0152|P0.2104:7628:4.40 C0.6:core:4.36 P0.2104:7628:4.40",
    "4|1.2|1|1|0.035|0.03|P0.203:7628:4.40 C0.7:core:4.53 P0.203:7628:4.40",
    "4|1.2|1|2|0.035|0.061|P0.2005:3313+2116:4.16 C0.55:core:4.41 P0.2005:2116+3313:4.16",
    "4|1.2|2|0.5|0.07|0.0152|P0.2104:7628:4.40 C0.6:core:4.36 P0.2104:7628:4.40",
    "4|1.2|2|1|0.07|0.03|P0.203:7628:4.40 C0.6:core:4.36 P0.203:7628:4.40",
    "4|1.2|2|2|0.07|0.061|P0.1835:3313+3313:4.10 C0.55:core:4.41 P0.1835:3313+3313:4.10",
    "4|1.6|1|0.5|0.035|0.0152|P0.2104:7628:4.40 C1.065:core:4.43 P0.2104:7628:4.40",
    "4|1.6|1|1|0.035|0.03|P0.203:7628:4.40 C1.03:core:4.43 P0.203:7628:4.40",
    "4|1.6|1|2|0.035|0.061|P0.2005:3313+2116:4.16 C0.96:core:4.43 P0.2005:2116+3313:4.16",
    "4|1.6|2|0.5|0.07|0.0152|P0.2104:7628:4.40 C1.065:core:4.43 P0.2104:7628:4.40",
    "4|1.6|2|1|0.07|0.03|P0.203:7628:4.40 C1.03:core:4.43 P0.203:7628:4.40",
    "4|1.6|2|2|0.07|0.061|P0.1835:3313+3313:4.10 C0.96:core:4.43 P0.1835:3313+3313:4.10",
    "4|2|1|0.5|0.035|0.0152|P0.2104:7628:4.40 C1.465:core:4.43 P0.2104:7628:4.40",
    "4|2|1|1|0.035|0.03|P0.203:7628:4.40 C1.43:core:4.43 P0.203:7628:4.40",
    "4|2|1|2|0.035|0.061|P0.2005:3313+2116:4.16 C1.36:core:4.43 P0.2005:2116+3313:4.16",
    "4|2|2|0.5|0.07|0.0152|P0.2104:7628:4.40 C1.465:core:4.43 P0.2104:7628:4.40",
    "4|2|2|1|0.07|0.03|P0.203:7628:4.40 C1.43:core:4.43 P0.203:7628:4.40",
    "4|2|2|2|0.07|0.061|P0.1605:3313+1080:4.10 C1.36:core:4.43 P0.1605:1080+3313:4.10",
    "6|0.8|1|0.5|0.035|0.0152|P0.1164:2116:4.16 C0.13:core:4.17 P0.2104:7628:4.40 C0.13:core:4.17 P0.1164:2116:4.16",
    "6|0.8|1|1|0.035|0.03|P0.092:3313:4.10 C0.1:core:4.36 P0.218:2116+2116:4.16 C0.1:core:4.36 P0.092:3313:4.10",
    "6|0.8|2|0.5|0.07|0.0152|P0.0764:1080:3.91 C0.13:core:4.17 P0.2104:7628:4.40 C0.13:core:4.17 P0.0764:1080:3.91",
    "6|0.8|2|1|0.07|0.03|P0.071:1080:3.91 C0.13:core:4.17 P0.142:1080+1080:3.91 C0.13:core:4.17 P0.071:1080:3.91",
    "6|1|1|0.5|0.035|0.0152|P0.0994:3313:4.10 C0.25:core:4.23 P0.2104:7628:4.40 C0.25:core:4.23 P0.0994:3313:4.10",
    "6|1|1|1|0.035|0.03|P0.109:2116:4.16 C0.1:core:4.36 P0.406:7628+7628:4.40 C0.1:core:4.36 P0.109:2116:4.16",
    "6|1|1|2|0.035|0.061|P0.1415:1080+1080:3.91 C0.1:core:4.36 P0.197:1080+1080+1080:3.91 C0.1:core:4.36 P0.1415:1080+1080:3.91",
    "6|1|2|0.5|0.07|0.0152|P0.0784:1080:3.91 C0.2:core:4.36 P0.2388:2116+2116:4.16 C0.2:core:4.36 P0.0784:1080:3.91",
    "6|1|2|1|0.07|0.03|P0.069:1080:3.91 C0.1:core:4.36 P0.406:7628+7628:4.40 C0.1:core:4.36 P0.069:1080:3.91",
    "6|1|2|2|0.07|0.061|P0.1055:1080+106:3.92 C0.1:core:4.36 P0.197:1080+1080+1080:3.91 C0.1:core:4.36 P0.1055:106+1080:3.92",
    "6|1.2|1|0.5|0.035|0.0152|P0.0994:3313:4.10 C0.35:core:4.36 P0.1164:2116:4.16 C0.35:core:4.36 P0.0994:3313:4.10",
    "6|1.2|1|1|0.035|0.03|P0.203:7628:4.40 C0.1:core:4.36 P0.406:7628+7628:4.40 C0.1:core:4.36 P0.203:7628:4.40",
    "6|1.2|1|2|0.035|0.061|P0.1375:1080+1080:3.91 C0.15:core:4.36 P0.325:1080+7628+1080:4.40 C0.15:core:4.36 P0.1375:1080+1080:3.91",
    "6|1.2|2|0.5|0.07|0.0152|P0.0994:3313:4.10 C0.35:core:4.36 P0.0994:3313:4.10 C0.35:core:4.36 P0.0994:3313:4.10",
    "6|1.2|2|1|0.07|0.03|P0.092:3313:4.10 C0.25:core:4.23 P0.218:2116+2116:4.16 C0.25:core:4.23 P0.092:3313:4.10",
    "6|1.2|2|2|0.07|0.061|P0.1375:1080+1080:3.91 C0.15:core:4.36 P0.231:1080+2116+1080:4.16 C0.15:core:4.36 P0.1375:1080+1080:3.91",
    "6|1.6|1|0.5|0.035|0.0152|P0.0994:3313:4.10 C0.55:core:4.41 P0.1164:2116:4.16 C0.55:core:4.41 P0.0994:3313:4.10",
    "6|1.6|1|1|0.035|0.03|P0.203:7628:4.40 C0.25:core:4.23 P0.513:7628+3313+7628:4.40 C0.25:core:4.23 P0.203:7628:4.40",
    "6|1.6|1|2|0.035|0.061|P0.1375:1080+1080:3.91 C0.35:core:4.36 P0.325:1080+7628+1080:4.40 C0.35:core:4.36 P0.1375:1080+1080:3.91",
    "6|1.6|2|0.5|0.07|0.0152|P0.0994:3313:4.10 C0.55:core:4.41 P0.0994:3313:4.10 C0.55:core:4.41 P0.0994:3313:4.10",
    "6|1.6|2|1|0.07|0.03|P0.203:7628:4.40 C0.25:core:4.23 P0.406:7628+7628:4.40 C0.25:core:4.23 P0.203:7628:4.40",
    "6|1.6|2|2|0.07|0.061|P0.1375:1080+1080:3.91 C0.35:core:4.36 P0.231:1080+2116+1080:4.16 C0.35:core:4.36 P0.1375:1080+1080:3.91",
    "6|2|1|0.5|0.035|0.0152|P0.0994:3313:4.10 C0.7:core:4.53 P0.2104:7628:4.40 C0.7:core:4.53 P0.0994:3313:4.10",
    "6|2|1|1|0.035|0.03|P0.092:3313:4.10 C0.7:core:4.53 P0.218:2116+2116:4.16 C0.7:core:4.53 P0.092:3313:4.10",
    "6|2|1|2|0.035|0.061|P0.1375:1080+1080:3.91 C0.55:core:4.41 P0.311:2116+2116+2116:4.16 C0.55:core:4.41 P0.1375:1080+1080:3.91",
    "6|2|2|0.5|0.07|0.0152|P0.0994:3313:4.10 C0.7:core:4.53 P0.2104:7628:4.40 C0.7:core:4.53 P0.0994:3313:4.10",
    "6|2|2|1|0.07|0.03|P0.203:7628:4.40 C0.45:core:4.36 P0.406:7628+7628:4.40 C0.45:core:4.36 P0.203:7628:4.40",
    "6|2|2|2|0.07|0.061|P0.1375:1080+1080:3.91 C0.55:core:4.41 P0.231:1080+2116+1080:4.16 C0.55:core:4.41 P0.1375:1080+1080:3.91",
    "8|0.8|1|0.5|0.035|0.0152|P0.0764:1080:3.91 C0.075:core:3.99 P0.1164:2116:4.16 C0.075:core:3.99 P0.1164:2116:4.16 C0.075:core:3.99 P0.0764:1080:3.91",
    "8|0.8|2|0.5|0.07|0.0152|P0.0764:1080:3.91 C0.075:core:3.99 P0.0994:3313:4.10 C0.075:core:3.99 P0.0994:3313:4.10 C0.075:core:3.99 P0.0764:1080:3.91",
    "8|1|1|0.5|0.035|0.0152|P0.0994:3313:4.10 C0.13:core:4.17 P0.1164:2116:4.16 C0.13:core:4.17 P0.1164:2116:4.16 C0.13:core:4.17 P0.0994:3313:4.10",
    "8|1|1|1|0.035|0.03|P0.069:1080:3.91 C0.075:core:3.99 P0.218:2116+2116:4.16 C0.075:core:3.99 P0.218:2116+2116:4.16 C0.075:core:3.99 P0.069:1080:3.91",
    "8|1|2|0.5|0.07|0.0152|P0.0994:3313:4.10 C0.13:core:4.17 P0.0994:3313:4.10 C0.13:core:4.17 P0.0994:3313:4.10 C0.13:core:4.17 P0.0994:3313:4.10",
    "8|1|2|1|0.07|0.03|P0.092:3313:4.10 C0.075:core:3.99 P0.138:1080+1080:3.91 C0.075:core:3.99 P0.138:1080+1080:3.91 C0.075:core:3.99 P0.092:3313:4.10",
    "8|1.2|1|0.5|0.035|0.0152|P0.0994:3313:4.10 C0.2:core:4.36 P0.1164:2116:4.16 C0.2:core:4.36 P0.1164:2116:4.16 C0.2:core:4.36 P0.0994:3313:4.10",
    "8|1.2|1|1|0.035|0.03|P0.092:3313:4.10 C0.1:core:4.36 P0.218:2116+2116:4.16 C0.1:core:4.36 P0.218:2116+2116:4.16 C0.1:core:4.36 P0.092:3313:4.10",
    "8|1.2|2|0.5|0.07|0.0152|P0.0994:3313:4.10 C0.2:core:4.36 P0.0994:3313:4.10 C0.2:core:4.36 P0.0994:3313:4.10 C0.2:core:4.36 P0.0994:3313:4.10",
    "8|1.2|2|1|0.07|0.03|P0.069:1080:3.91 C0.15:core:4.36 P0.138:1080+1080:3.91 C0.15:core:4.36 P0.138:1080+1080:3.91 C0.15:core:4.36 P0.069:1080:3.91",
    "8|1.6|1|0.5|0.035|0.0152|P0.1164:2116:4.16 C0.3:core:4.41 P0.1528:1080+1080:3.91 C0.3:core:4.41 P0.1528:1080+1080:3.91 C0.3:core:4.41 P0.1164:2116:4.16",
    "8|1.6|1|1|0.035|0.03|P0.109:2116:4.16 C0.25:core:4.23 P0.218:2116+2116:4.16 C0.25:core:4.23 P0.218:2116+2116:4.16 C0.25:core:4.23 P0.109:2116:4.16",
    "8|1.6|2|0.5|0.07|0.0152|P0.1164:2116:4.16 C0.3:core:4.41 P0.1164:2116:4.16 C0.3:core:4.41 P0.1164:2116:4.16 C0.3:core:4.41 P0.1164:2116:4.16",
    "8|1.6|2|1|0.07|0.03|P0.203:7628:4.40 C0.2:core:4.36 P0.138:1080+1080:3.91 C0.2:core:4.36 P0.138:1080+1080:3.91 C0.2:core:4.36 P0.203:7628:4.40",
    "8|2|1|0.5|0.035|0.0152|P0.2104:7628:4.40 C0.35:core:4.36 P0.2104:7628:4.40 C0.35:core:4.36 P0.2104:7628:4.40 C0.35:core:4.36 P0.2104:7628:4.40",
    "8|2|1|1|0.035|0.03|P0.203:7628:4.40 C0.2:core:4.36 P0.406:7628+7628:4.40 C0.2:core:4.36 P0.406:7628+7628:4.40 C0.2:core:4.36 P0.203:7628:4.40",
    "8|2|2|0.5|0.07|0.0152|P0.2104:7628:4.40 C0.3:core:4.41 P0.2104:7628:4.40 C0.3:core:4.41 P0.2104:7628:4.40 C0.3:core:4.41 P0.2104:7628:4.40",
    "8|2|2|1|0.07|0.03|P0.203:7628:4.40 C0.3:core:4.41 P0.184:3313+3313:4.10 C0.3:core:4.41 P0.184:3313+3313:4.10 C0.3:core:4.41 P0.203:7628:4.40",
    "8|2|2|2|0.07|0.061|P0.3555:7628+1080+1080:4.40 C0.15:core:4.36 P0.191:1080+1080+1080:3.91 C0.15:core:4.36 P0.191:1080+1080+1080:3.91 C0.15:core:4.36 P0.3555:1080+1080+7628:4.40"
};
int JR_NSTACK = 77;
